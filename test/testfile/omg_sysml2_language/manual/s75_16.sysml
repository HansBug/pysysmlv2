package P9 {
    item A;
    comment Comment1 about A
        /* This is a comment about item A. */

    comment Comment2
        /* This is a comment about package P9. */

    /* This is also a comment about package P9. */

    doc P9_Doc
        /* This is documentation about package P9. */
}
