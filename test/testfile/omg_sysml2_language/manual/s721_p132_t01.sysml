concern concern1 {
    subject system1;
    stakeholder operator;
}
constraint assumption1 { /*...*/ }
requirement requirement1 {
    frame concern1;
    assume assumption1;
    require constraint req1Formalization;
}
