case def FaultRecovery {
    subject system : AutomationSystem;
    actor engineer : Person;
    objective {
        doc
        /* The engineer determines the cause of the system
         * fault and resolves it returning the system to
         * nominal operation.
         */
    }
}
