part def VehicleDynamics {
    attribute C_d : Real;
    attribute C_f : Real;
    attribute wheelPower : PowerValue;
    attribute mass : MassValue;
    action straightLineDynamics { in delta_t : TimeValue;
        in v_in : SpeedValue; in x_in : LengthValue;
        // Values are bound to the parameters of calculation usages (similar to action parameters).
        calc acc : Acceleration {
            // A calculation definition can also be invoked as an expression, with input values given as arguments, evaluating to the result of the calculation.
            in tp = Power(wheelPower, C_d, C_f, mass, v_in);
            in tm = mass;
            in v = v_in;
            return a;
        }
        calc vel : Velocity {
            in dt = delta_t;
            in v0 = v_in;
            in a = acc.a;
            return v;
        }
        calc pos : Position {
            in dt = delta_t;
            in x0 = x_in;
            in v = vel.v;
            return x;
        }
        // Calculation results can be referenced by name (they are output parameters).
        out v_out : SpeedValue = vel.v;
        out x_out : LengthValue = pos.x;
    }
}
