standard library package NaturalFunctions {
    public import ScalarValues::*;
    function '+' specializes IntegerFunctions::'+' {in x: Natural[1]; in y: Natural[0..1]; return : Natural[1];}
    function '*' specializes IntegerFunctions::'*' {in x: Natural[1]; in y: Natural[1]; return : Natural[1];}
    function '/' specializes IntegerFunctions::'/' {in x: Natural[1]; in y: Natural[1]; return : Natural[1];}
    function '%' specializes IntegerFunctions::'%' {in x: Natural[1]; in y: Natural[1]; return : Natural[1];}
    function '<' specializes IntegerFunctions::'<' {in x: Natural[1]; in y: Natural[1]; return : Boolean[1];}
    function '>' specializes IntegerFunctions::'>' {in x: Natural[1]; in y: Natural[1]; return : Boolean[1];}
    function '<=' specializes IntegerFunctions::'<=' {in x: Natural[1]; in y: Natural[1]; return : Boolean[1];}
    function '>=' specializes IntegerFunctions::'>=' {in x: Natural[1]; in y: Natural[1]; return : Boolean[1];}
    function max specializes IntegerFunctions::max {in x: Natural[1]; in y: Natural[1]; return : Natural[1];}
    function min specializes IntegerFunctions::min { n x: Natural[1]; in y: Natural[1]; return : Natural[1];}
    function '==' specializes IntegerFunctions::'=='
    {in x: Natural[0..1]; in y: Natural[0..1]; return : Boolean[1];}
    function ToString specializes IntegerFunctions::ToString {in x: Natural[1]; return : String[1];}
    function ToNatural{in x: String[1]; return : Natural[1];}
}
