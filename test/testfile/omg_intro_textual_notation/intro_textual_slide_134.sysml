standard library package IntegerFunctions {
    public import ScalarValues::*;
    function abs specializes RationalFunctions::abs {in x: Integer[1]; return : Natural[1];}
    function '+' specializes RationalFunctions::'+' {in x: Integer[1]; in y: Integer[0..1]; return : Integer[1];}
    function '-' specializes RationalFunctions::'-' {in x: Integer[1]; in y: Integer[0..1]; return : Integer[1];}
    function '*' specializes RationalFunctions::'*' {in x: Integer[1]; in y: Integer[1]; return : Integer[1];}
    function '/' specializes RationalFunctions::'/' {in x: Integer[1]; in y: Integer[1]; return : Rational[1];}
    function '**' specializes RationalFunctions::'**' {in x: Integer[1]; in y: Natural[1]; return : Integer[1];}
    function '^' specializes RationalFunctions::'^' {in x: Integer[1]; in y: Natural[1]; return : Integer[1];}
    function '%' specializes NumericalFunctions::'%' {in x: Integer[1]; in y: Integer[1]; return : Integer[1];}
    function '<' specializes RationalFunctions::'<' {in x: Integer[1]; in y: Integer[1]; return : Boolean[1];}
    function '>' specializes RationalFunctions::'>' {in x: Integer[1]; in y: Integer[1]; return : Boolean[1];}
    function '<=' specializes RationalFunctions::'<=' {in x: Integer[1]; in y: Integer[1]; return : Boolean[1];}
    function '>=' specializes RationalFunctions::'>=' {in x: Integer[1]; in y: Integer[1]; return : Boolean[1];}
    function max specializes RationalFunctions::max {in x: Integer[1]; in y: Integer[1]; return : Integer[1];}
    function min specializes RationalFunctions::min {in x: Integer[1]; in y: Integer[1]; return : Integer[1];}
    function '==' specializes DataFunctions::'==' {in x: Integer[0..1]; in y: Integer[0..1]; return : Boolean[1];}
    function '..' specializes ScalarFunctions::'..'
    {in lower: Integer[1]; in upper: Integer[1]; return : Integer[0..*];}
    function ToString specializes RationalFunctions::ToString {in x: Integer[1]; return : String[1];}
    function ToNatural {in x: Integer[1]; return : Natural[1];}
    function ToInteger {in x: String[1]; return : Integer[1];}
    function sum specializes RationalFunctions::sum {in collection: Integer[0..*]; return : Integer[1];}
    function product specializes RationalFunctions::product {in collection: Integer[0..*]; return : Integer[1];}
}
